module ietf-interfaces-ext {

    namespace "urn:ietf:params:xml:ns:yang:ietf-interfaces-ext";
    prefix if-ext;
    import ietf-yang-types {
        prefix yang;
    }
     import ietf-interfaces {
        prefix if;
     }
    organization
        "IETF NETMOD (NETCONF Data Modeling Language) Working Group";

    contact
        "WG Web:   <http://tools.ietf.org/wg/netmod/>
        WG List:  <mailto:netmod@ietf.org>

        WG Chair: David Kessens
        <mailto:david.kessens@nsn.com>

        WG Chair: Juergen Schoenwaelder
        <mailto:j.schoenwaelder@jacobs-university.de>


        Editor:   Martin Bjorklund
        <mailto:mbj@tail-f.com>";
    description
        "augments needed for IOS-XE platform show interface command";

    augment "/if:interfaces-state/if:interface/if:statistics" {
        description
        "this adds a leaf called total input packets as we have no way of doing arithmetic in RPL";

        leaf in-pkts {
            type yang:counter64;
            description
                "total packets input";
        }

        leaf out-pkts {
            type yang:counter64;
            description
                "total packets output";
        }
    }

        augment "/if:interfaces-state/if:interface" {
                description
                "This augment adds a container which describes the bandwidth information of an interface.";

                container bandwidth {
                        description
                                "Bandwidth data for an interface.";

                        leaf value {
                                type uint64;
                                description
                                        "Raw value for the bandwidth.";
                        }

                        leaf units {
                                type string;
                                description
                                        "Units of the bandwidth.";
                        }

                }
        }

}
