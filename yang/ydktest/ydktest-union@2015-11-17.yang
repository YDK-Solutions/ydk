module ydktest-union {

  /*** NAMESPACE / PREFIX DEFINITION ***/

  namespace "http://cisco.com/ns/yang/ydktest-union";


  prefix "ydkut";

  /*** LINKAGE (IMPORTS / INCLUDES) ***/

  //import ietf-inet-types { prefix "inet"; }

  //import Cisco-IOS-XR-types { prefix "xr"; }



  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for unions
    

     Copyright (c) 2013-2014 by Cisco Systems, Inc.
     All rights reserved.";

  revision "2015-11-17" {
    description
      "Initial revision.";
  }


  
 typedef Ydk-Enum-test {
    type enumeration {
      enum not-set {
        value 0;
        description "Not Set";
      }
      enum none {
        value 1;
        description "None";
      }
      enum local {
        value 2;
        description "Local";
      }
      enum remote {
        value 3;
        description "Remote";
      }
    }
    description "YDK Enum test";
  }
   
container built-in-t {
     
     description "config for built-in types";
        

     leaf younion {
          type union {
            type Ydk-Enum-test;
            type uint32 {
              range "0..63";
            }
          }
     
        }
}
}
